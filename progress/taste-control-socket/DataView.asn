TASTE-Dataview DEFINITIONS ::=
BEGIN
IMPORTS T-Int32, T-UInt32, T-Int8, T-UInt8, T-Boolean FROM TASTE-BasicTypes;

-- A few simple types to start with ASN.1
MyInteger   ::= T-UInt8

MyReal      ::= REAL (-1000 .. 100000)

MyBool      ::= BOOLEAN

MyEnum      ::= ENUMERATED { hello, world, howareyou }

MySeq       ::= SEQUENCE {
    input-data  MyInteger,
    output-data MyInteger,
    validity    ENUMERATED { valid, invalid }
}

MySensorData ::= SEQUENCE {
    yawAct MyReal,
    pitchAct MyReal,
    rollAct MyReal,
    baropAct MyReal,
    accxAct MyReal,
    accyAct MyReal,
    acczAct MyReal
}

MyDroneData ::= SEQUENCE {
    yawrateRef MyReal,
    pitchRef MyReal,
    rollRef MyReal,
    thrustRef MyReal
}

MyChoice    ::= CHOICE {
    a BOOLEAN,
    b MySeq
}

MySeqOf     ::= SEQUENCE (SIZE (2)) OF MyEnum

MyOctStr    ::= OCTET STRING (SIZE (3))

-- You can also declare constants
myVar       MySeqOf     ::= { hello, world }

END
