TASTE-Dataview DEFINITIONS ::=
BEGIN
IMPORTS T-Int32, T-UInt32, T-Int8, T-UInt8, T-Boolean FROM TASTE-BasicTypes;

-- A few simple types to start with ASN.1
MyInteger   ::= T-UInt8

MyReal      ::= REAL (0.0 .. 1000.0)

MyPWM       ::= SEQUENCE{
    pwm1 MyReal,
    pwm2 MyReal,
    pwm3 MyReal,
    pwm4 MyReal
}

MyTrajectory ::=SEQUENCE{
    x MyReal,
    y MyReal,
    z MyReal,
    yaw MyReal
}

MyStates    ::=SEQUENCE{
    x MyReal,
    y MyReal,
    z MyReal,
    yaw MyReal,
    pitch MyReal,
    roll MyReal,
    dx MyReal,
    dy MyReal,
    dz MyReal,
    dyaw MyReal,
    dpitch MyReal,
    droll MyReal
}

MyBool      ::= BOOLEAN

MyEnum      ::= ENUMERATED { hello, world, howareyou }

MySeq       ::= SEQUENCE {
    input-data  MyInteger,
    output-data MyInteger,
    validity    ENUMERATED { valid, invalid }
}

MyChoice    ::= CHOICE {
    a BOOLEAN,
    b MySeq
}

MySeqOf     ::= SEQUENCE (SIZE (2)) OF MyEnum

MyOctStr    ::= OCTET STRING (SIZE (3))

-- You can also declare constants
myVar       MySeqOf     ::= { hello, world }

END

TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

END
