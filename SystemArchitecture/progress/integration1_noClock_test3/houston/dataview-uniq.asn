TASTE-Dataview DEFINITIONS ::=
BEGIN
IMPORTS T-Int32, T-UInt32, T-Int8, T-UInt8, T-Boolean FROM TASTE-BasicTypes;

--declerations of global variables
--AgentNumber   T-UInt8  
--pathLocationNumber  T-UInt8  
--nodeNumber          T-UInt8  
--actionmaxNumber     T-UInt8  



-- A few simple types to start with ASN.1
MyInteger   ::= T-UInt8

MyReal      ::= REAL (-1000.0 .. 100000.0)

MyBool      ::= BOOLEAN

MyEnum      ::= ENUMERATED { hello, world, howareyou }

MySeq       ::= SEQUENCE {
    input-data  MyInteger,
    output-data MyInteger,
    validity    ENUMERATED { valid, invalid }
}

--User Commands (in alphabetical order)
Acceleration ::= SEQUENCE {
    aX MyReal, 
    aY MyReal,
    aZ MyReal, 
    aRoll MyReal,
    aPitch MyReal,
    aYaw MyReal
}

Agent ::= SEQUENCE {
    agentID T-Int8,
    agentColor Color,
    currentPosition Position,
    currentOrientation Orientation,
    currentVelocity Velocity,
    currentAcceleration Acceleration
}

MultiAgents ::= SEQUENCE {
    agents SEQUENCE (SIZE (5)) OF Agent
}

MultiDroneSensorData ::= SEQUENCE {
    data SEQUENCE (SIZE (5)) OF DroneSensorData
}

MultiDroneControllerInput ::= SEQUENCE {
    controllerInput SEQUENCE (SIZE (5)) OF DroneControllerInput
}

Area ::= SEQUENCE {
    height T-Int8,
    width T-Int8,
    depth T-Int8,
    refLocation Position
}

Color ::= ENUMERATED {black, pink, red}

DroneControllerInput ::= SEQUENCE {
    yawrateRef MyReal,
    pitchRef MyReal,
    rollRef MyReal,
    heightRef MyReal,
    thrustRef MyReal
}

DroneSensorData ::= SEQUENCE {
    yawAct MyReal,
    pitchAct MyReal,
    rollAct MyReal,
    baropAct MyReal,
    accxAct MyReal,
    accyAct MyReal,
    acczAct MyReal
}

FeedbackToGUI ::= SEQUENCE {
    flight WorldData,
    notification SystemState
}

HoverAction ::= SEQUENCE {
    yaw-rate MyReal,
    duration MyReal
}

MyChoice    ::= CHOICE {
    a BOOLEAN,
    b MySeq
}

Orientation ::= SEQUENCE{
    roll MyReal,
    pitch MyReal,
    yaw MyReal
}

Position ::= SEQUENCE {
    x MyReal,
    y MyReal,
    z MyReal
}

PositionSystemData ::= SEQUENCE {
    xAct MyReal,
    yAct MyReal
}

ReferenceFormation ::= SEQUENCE {
    --name STRING,
    nodes SEQUENCE (SIZE (5)) OF T-Int8, -- AgentID
    anchor T-Int8, --AgentID
    formationAnchorPosition Position
}

ReferencePath ::= SEQUENCE {
    locations SEQUENCE (SIZE (3)) OF Position,
    actions SEQUENCE (SIZE (3)) OF HoverAction
}

PixyData ::= SEQUENCE{
    xPix T-UInt32,
    yPix T-UInt32
}

SafetyEvent ::= ENUMERATED {safe,collision,wallColl,ceilColl}

SystemState ::= ENUMERATED {idle, initializing, runningOk, emergencyLand, safeReturn}

Trajectory ::= SEQUENCE{
    x MyReal,
    y MyReal,
    z MyReal,
    yaw MyReal
}

UserCommand ::= ENUMERATED {sysStart, sysPause, sysStop}

Velocity ::= SEQUENCE {
    vX MyReal, 
    vY MyReal,
    vZ MyReal, 
    vRoll MyReal,
    vPitch MyReal,
    vYaw MyReal
}

WorldData ::= SEQUENCE{
    agentData Agent
}
--WorldData ::= SEQUENCE {
--    myArea Area,
--    refPath ReferencePath,
    --refFormation ReferenceFormation,
    --agents SEQUENCE (SIZE (3)) OF Agent
--}





MySeqOf     ::= SEQUENCE (SIZE (2)) OF MyEnum

MyOctStr    ::= OCTET STRING (SIZE (3))

-- You can also declare constants
myVar       MySeqOf     ::= { hello, world }

END

TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

END
